FME workspace drugie_zadaniue.fmw

Parameters:
- SourceDataset_GDAL_GENERIC_RASTER = $(FME_MF_DIR)ras250_gb\data\*   # Source GDAL Raster File(s)
- DestDataset_GEODATABASE_FILE_4 = $(FME_MF_DIR)Results6.gdb   # File Geodatabase

Readers:
- GDAL_GENERIC_RASTER_1: GDAL_GENERIC_RASTER from $(SourceDataset_GDAL_GENERIC_RASTER)

Writers:
- GEODATABASE_FILE_3: GEODATABASE_FILE to $(DestDataset_GEODATABASE_FILE_4)

GDAL_GENERIC_RASTER (reader GDAL_GENERIC_RASTER_1)
    -> Reprojector
Reprojector
    DEST = EPSG:4326
    INTERPOLATION_TYPE = NearestNeighbor
    RASTER_CELL_SIZE = PreserveCells
    RASTER_TOLERANCE = 0.0
    REPROJECTED -> RasterPropertyExtractor_2
RasterPropertyExtractor_2
    -> AttributeCreator
AttributeCreator
    ATTR_TABLE = SET_TO NewName (varchar(200)) = @Value(fme_basename)_@Value(_num_rows)x@Value(_num_columns)
    INPUT_PORT_CONNECTED = CONNECTED
    -> RasterExtentsCoercer
RasterExtentsCoercer
    EXTENTS_TYPE_LOOKUP = RasterExtents
    EXTENTS_TYPE = Raster Extents
    EXTENTS -> Extents (writer GEODATABASE_FILE_3)
Extents (writer GEODATABASE_FILE_3)
    attributes: NewName char(200), _num_bands double, _num_rows double, _num_columns double, _spacing_x double, _spacing_y double, _origin_x double, _origin_y double, _rotation_x double, _rotation_y double, _min_x double, _min_y double, _max_x double, _max_y double, _cell_origin_x double, _cell_origin_y double, _upper_left_x double, _upper_left_y double, _upper_right_x double, _upper_right_y double, _lower_right_x double, _lower_right_y double, _lower_left_x double, _lower_left_y double
