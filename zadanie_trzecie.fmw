FME workspace zadanie_trzecie.fmw

Parameters:
- SourceDataset_OGCGEOPACKAGE = $(FME_MF_DIR)bdline_gpkg_gb\Data\bdline_gb.gpkg   # GeoPackage File
- DestDataset_GEODATABASE_FILE_MOSAIC_DATASET = $(FME_MF_DIR)wynikwhatever.gdb   # File Geodatabase
- SourceDataset_GEOTIFF = $(FME_MF_DIR)ras250_gb\data\*.tif   # Source GeoTIFF File(s) or URL(s)
- DestDataset_POSTGIS_RASTER = pgadmin   # Connection

Readers:
- OGCGEOPACKAGE_1: OGCGEOPACKAGE from $(SourceDataset_OGCGEOPACKAGE)
- GEOTIFF_2: GEOTIFF from $(SourceDataset_GEOTIFF)

Writers:
- GEODATABASE_FILE_MOSAIC_DATASET_1: GEODATABASE_FILE_MOSAIC_DATASET to $(DestDataset_GEODATABASE_FILE_MOSAIC_DATASET)
- POSTGIS_RASTER_1: POSTGIS_RASTER to $(DestDataset_POSTGIS_RASTER)

scotland_and_wales_region (reader OGCGEOPACKAGE_1)
    attributes: Name text(100), Area_Code text(3), Area_Description text(50), File_Name text(100), Feature_Serial_Number mediumint, Collection_Serial_Number mediumint, Global_Polygon_ID mediumint, Admin_Unit_ID mediumint, Census_Code text(9), Hectares double, Non_Inland_Area double, Area_Type_Code text(2), Area_Type_Description text(25), Non_Area_Type_Code text(3), Non_Area_Type_Description text(36), fid int,PrimaryKey
    -> Tester
Tester
    BOOL_OP = OR
    TEST_CLAUSE = CASE_INSENSITIVE_TEST @Value(File_Name) CONTAINS SOUTH_WALES
    TEST_MODE = TEST
    PASSED -> Clipper [CLIPPER]
GEOTIFF (reader GEOTIFF_2)
    -> RasterPaletteRemover
RasterPaletteRemover
    -> Clipper [CANDIDATE]
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> exports (writer POSTGIS_RASTER_1)
exports (writer POSTGIS_RASTER_1)
    attributes: _clipped char(3)
